[DOCUMENT]
TITLE: B0 G1.5-B structured requirements-tooling pilot
UID: PILOT-ONLY-DOCUMENT
VERSION: @GIT_VERSION (Git branch: @GIT_BRANCH)
CLASSIFICATION: Internal
PREFIX: PILOT-ONLY-
OPTIONS:
  MARKUP: Text

[REQUIREMENT]
UID: PILOT-ONLY-NEED-01
LEVEL: user_need
STATUS: pilot_only_candidate
TAGS: phase_one, non_authoritative
TITLE: Bounded attitude experiment use
STATEMENT: >>>
The B0 system shall support a configured, repeatable bounded attitude experiment for engineering review without claiming full-flight capability.
<<<
RATIONALE: >>>
This is a source-format trial of a user-need record. It is not a formal B0 requirement and is not part of coverage accounting.
<<<
COMMENT: >>>
Generated review projection; edit pilot_structure.json, not this file.
<<<

[REQUIREMENT]
UID: PILOT-ONLY-INTERFACE-02
LEVEL: system_constraint
STATUS: pilot_only_candidate
TAGS: phase_one, interface, truth_boundary
TITLE: Runtime truth isolation
STATEMENT: >>>
After explicit reset initialization, the estimator and controller shall not receive live truth as a runtime input; truth is limited to plant, sensor, and evaluation responsibilities.
<<<
RATIONALE: >>>
This trial represents an interface constraint and a child relationship without treating existing component behavior as the sole source of the obligation.
<<<
COMMENT: >>>
Generated review projection; edit pilot_structure.json, not this file.
<<<
RELATIONS:
- TYPE: Parent
  VALUE: PILOT-ONLY-NEED-01

[REQUIREMENT]
UID: PILOT-ONLY-ACCEPTANCE-03
LEVEL: system_constraint
STATUS: pilot_only_candidate
TAGS: phase_one, acceptance, configuration_reference
TITLE: Frozen acceptance-field reference
STATEMENT: >>>
Any assessment of the signed three-axis step scenario shall cite the approved G0 v2 configuration fields for its event window and metrics instead of copying numerical thresholds into a second requirement source.
<<<
RATIONALE: >>>
This trial represents a performance/acceptance reference while preserving the JSON contract as the sole parameter source and avoiding a false performance result.
<<<
COMMENT: >>>
Generated review projection; edit pilot_structure.json, not this file.
<<<
RELATIONS:
- TYPE: Parent
  VALUE: PILOT-ONLY-NEED-01

[REQUIREMENT]
UID: PILOT-ONLY-LEGACY-04
LEVEL: applicability_record
STATUS: pilot_only_candidate
TAGS: phase_one, legacy, not_applicable
TITLE: Preserved legacy control applicability
STATEMENT: >>>
For current B0, the applicability record shall preserve CTL-REQ-001 and CTL-REQ-002 unchanged and record their approved not-applicable status without claiming that either legacy performance threshold is satisfied.
<<<
RATIONALE: >>>
This trial represents a non-applicable legacy relationship. The legacy identifiers remain references only and are never candidate identifiers for reuse.
<<<
COMMENT: >>>
Generated review projection; edit pilot_structure.json, not this file.
<<<
RELATIONS:
- TYPE: Parent
  VALUE: PILOT-ONLY-NEED-01

[REQUIREMENT]
UID: PILOT-ONLY-G2-05
LEVEL: component_constraint
STATUS: pilot_only_candidate
TAGS: phase_one, g2_planned, controller
TITLE: Planned controller interface boundary
STATEMENT: >>>
The planned G2 controller shall consume the declared command, state estimate, and paired actuator feedback; it shall expose requested torque, limited target, and saturation status under the approved reset and step contract.
<<<
RATIONALE: >>>
This is a planned component candidate used to test truthful planned/not-run status. It does not claim a G2 implementation or closed-loop evidence.
<<<
COMMENT: >>>
Generated review projection; edit pilot_structure.json, not this file.
<<<
RELATIONS:
- TYPE: Parent
  VALUE: PILOT-ONLY-INTERFACE-02
